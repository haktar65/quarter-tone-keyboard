"""Load or reload the QTKB helper library beside this macro."""

import importlib
import os
import sys


try:
    FREECAD_TOOLS_PATH = os.path.dirname(os.path.abspath(__file__))
except NameError as error:
    raise RuntimeError(
        "Run this file through FreeCAD's Macro dialog so its location is known."
    ) from error

if FREECAD_TOOLS_PATH not in sys.path:
    sys.path.insert(0, FREECAD_TOOLS_PATH)

importlib.invalidate_caches()
import qtkb

qtkb = importlib.reload(qtkb)
qtkb.reload()
print(
    "QTKB helper library loaded from: "
    f"{FREECAD_TOOLS_PATH}. Use qtkb.<module>.<function>(...)."
)
